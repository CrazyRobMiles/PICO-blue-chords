import Mesh
import Part
from FreeCAD import Base
import sys

import math
import random


keyPushHeight=2.5
keySocketHoleHeight=9.4
keyswitchHoleSize = 15.3
keyInsetHoleMargin = 5.5
displayHoleMargin = 3.5

displayHoleWidth=28.0
displayHoleDepth=16.0
picoMargin = 3.0
picoInsetHeight = keyPushHeight+keySocketHoleHeight-2
picoLowerDepth = 12.0
displayInsetHeight=keySocketHoleHeight
caseHeight = 15.0

baseHeight = 17.0
baseSidethickness = 3.0
baseYOffset = -50;

boxSideThickness=2.0
boxMargin = 3.0


end = [223.57,136.00]
origin = [104.09,35.51]

width=end[0] - origin[0]
depth=end[1] - origin[1]

mountingHoles = [[220.98,38.1],[106.68,38.1],[144.45,129.54],[182.88,129.54]]
holeRadius = 1.4
picoLowerDepth = 12.0

baseHoleRadius = 1.7
baseHoleHeadRadius = 3.1
baseHoleHeadDepth = 1.5
baseRimThickness = 1.0
baseRimHeight = 4.0

pico = ["A1",163.83,106.68,23.5,58.15]
Brd1 = ["Brd1",123.80,51.24,27.42,27.42]
Brd2 = ["Brd2",203.01,51.24,27.42,27.42]
Control_1 = ["Control_1",113.03,54.94,17.38,17.38]
Control_2 = ["Control_2",113.03,72.11,17.38,17.38]
Control_3 = ["Control_3",113.03,89.28,17.38,17.38]
Control_4 = ["Control_4",113.03,106.45,17.38,17.38]
Control_5 = ["Control_5",113.03,123.62,17.38,17.38]
Index_1 = ["Index_1",153.67,50.80,17.38,17.38]
Index_2 = ["Index_2",153.67,67.97,17.38,17.38]
Little_1 = ["Little_1",214.63,54.94,17.38,17.38]
Little_2 = ["Little_2",214.63,72.11,17.38,17.38]
Little_3 = ["Little_3",214.63,89.28,17.38,17.38]
Little_4 = ["Little_4",214.63,106.45,17.38,17.38]
Little_5 = ["Little_5",214.63,123.62,17.38,17.38]
Middle_1 = ["Middle_1",173.99,50.80,17.38,17.38]
Middle_2 = ["Middle_2",173.99,67.97,17.38,17.38]
Ring_1 = ["Ring_1",194.31,54.94,17.38,17.38]
Ring_2 = ["Ring_2",194.31,72.11,17.38,17.38]
Ring_3 = ["Ring_3",194.31,89.28,17.38,17.38]
Ring_4 = ["Ring_4",194.31,106.45,17.38,17.38]
Ring_5 = ["Ring_5",194.31,123.62,17.38,17.38]
Thumb_1 = ["Thumb_1",133.35,54.94,17.38,17.38]
Thumb_2 = ["Thumb_2",133.35,72.11,17.38,17.38]
Thumb_3 = ["Thumb_3",133.35,89.28,17.38,17.38]
Thumb_4 = ["Thumb_4",133.35,106.45,17.38,17.38]
Thumb_5 = ["Thumb_5",133.35,123.62,17.38,17.38]

# right handed flag
right_handed = True 
if right_handed:
	keyHoles = [Little_5,Ring_5, Middle_2, Index_1, Thumb_1,Control_2]
	displayHole = Brd2
else:
      keyHoles = [Little_3,Ring_2, Middle_1, Index_2, Thumb_5,Control_5]
      displayHole = Brd1

panelPos =  Base.Vector(origin[0]-boxMargin,origin[1]-boxMargin,0)
panel = Part.makeBox(width+(boxMargin*2),depth+(boxMargin*2),keyPushHeight,panelPos)

basePos =  Base.Vector(origin[0]-boxMargin,origin[1]-boxMargin,baseYOffset)
base = Part.makeBox(width+(boxMargin*2),depth+(boxMargin*2),baseHeight,basePos)
baseCutPos =  Base.Vector(origin[0]-boxMargin+baseSidethickness,origin[1]-boxMargin+baseSidethickness,baseYOffset+baseSidethickness)
baseCut = Part.makeBox(width+(boxMargin*2)-(baseSidethickness*2),depth+(boxMargin*2)-(baseSidethickness*2),baseHeight,baseCutPos)
base = base.cut(baseCut)

rimCutWidth = width+(boxMargin+2) - (2* baseRimThickness)
rimCutDepth = depth+(boxMargin+2) - (2* baseRimThickness)
rimCutPos = Base.Vector(origin[0]-boxMargin+(boxSideThickness- baseRimThickness), origin[1]-boxMargin+(boxSideThickness- baseRimThickness), baseYOffset+baseHeight-baseRimHeight)
rimCut = Part.makeBox(width+(boxMargin*2)- (2* baseRimThickness),depth+(boxMargin*2)- (2* baseRimThickness),baseHeight,rimCutPos)
base = base.cut(rimCut)

def cutHole(panel, item,width,depth, startHeight, height):
   holePos = Base.Vector(item[1]-width/2,item[2]-depth/2.0,startHeight)
   hole = Part.makeBox(width,depth,height,holePos)   
   panel = panel.cut(hole)
   return panel

def cutHoleOLED(panel, item,width,depth, startHeight, height):
   holePos = Base.Vector(item[1]-width/2,item[2]-depth/2.0,startHeight)
   hole = Part.makeBox(width,depth,height,holePos)   
   panel = panel.cut(hole)
   return panel

def cutHolePico(panel, item,width,depth, startHeight, height):
   holePos = Base.Vector(item[1]-width/2,item[2]-depth/2.0+2.5,startHeight-picoLowerDepth)
   hole = Part.makeBox(width,depth+20,height+picoLowerDepth,holePos)   
   panel = panel.cut(hole)
   return panel

for hole in mountingHoles:
   holePos = Base.Vector(hole[0],hole[1],0)
   holeCylinder = Part.makeCylinder(holeRadius,keyPushHeight,holePos)
   panel = panel.cut(holeCylinder)
   holePos = Base.Vector(hole[0],hole[1],baseYOffset)
   holeCylinder = Part.makeCylinder(baseHoleRadius,baseSidethickness,holePos)
   base = base.cut(holeCylinder)
   holeCylinder = Part.makeCylinder(baseHoleHeadRadius,baseHoleHeadDepth,holePos)
   base = base.cut(holeCylinder)

for keyHole in keyHoles:
   panel = cutHole(panel, keyHole, keyswitchHoleSize,keyswitchHoleSize,0,keyPushHeight);

insetPanelPos =  Base.Vector(origin[0]-boxMargin,origin[1]-boxMargin,keyPushHeight)
insetPanel = Part.makeBox(width+(boxMargin*2),depth+(boxMargin*2),keySocketHoleHeight,insetPanelPos)
for keyHole in keyHoles:
   insetPanel = cutHole(insetPanel, keyHole, keyswitchHoleSize+keyInsetHoleMargin,keyswitchHoleSize+keyInsetHoleMargin,keyPushHeight,keySocketHoleHeight);
panel = panel.fuse(insetPanel)

panel = cutHoleOLED(panel, displayHole, displayHole[3]+displayHoleMargin,displayHole[4]+displayHoleMargin,0,displayInsetHeight)
panel = cutHoleOLED(panel, displayHole,displayHoleWidth,displayHoleDepth,displayInsetHeight,displayInsetHeight)

outerPos =  Base.Vector(origin[0]-(boxSideThickness+boxMargin),origin[1]-(boxSideThickness+boxMargin),-caseHeight+keyPushHeight+keySocketHoleHeight)
outerExtraSize = (boxSideThickness+boxMargin)*2
outerBox = Part.makeBox(width+outerExtraSize,depth+outerExtraSize,caseHeight,outerPos)
innerPos =  Base.Vector(origin[0]-boxMargin,origin[1]-boxMargin,-caseHeight)
innerBox = Part.makeBox(width+(boxMargin*2),depth+(boxMargin*2),caseHeight,innerPos)
outerBox = outerBox.cut(innerBox)
innerPos =  Base.Vector(origin[0],origin[1],0)
innerBox = Part.makeBox(width,depth,keyPushHeight+keySocketHoleHeight,innerPos)
outerBox = outerBox.cut(innerBox)
completeBox = outerBox.fuse(panel)
completeBox = cutHolePico(completeBox, pico, pico[3]+picoMargin,pico[4]+picoMargin,0,picoInsetHeight)
panel = cutHolePico(panel, pico, pico[3]+picoMargin,pico[4]+picoMargin,0,picoInsetHeight)
base = cutHolePico(base, pico, pico[3]+picoMargin,pico[4]+picoMargin,baseYOffset+20,picoInsetHeight)

Part.show(panel)
Part.show(base)


Gui.SendMsgToActiveView("ViewFit")
Gui.activeDocument().activeView().viewAxometric()
